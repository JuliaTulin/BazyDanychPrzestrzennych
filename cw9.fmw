FME workspace cw9.fmw
Startup Python:
      import smtplib
      import fme
      import datetime

      sender_email =  fme.macroValues['email']
      receiver_email = fme.macroValues['emailKlienta']
      password = fme.macroValues['Hasło']
      county_name = fme.macroValues['nazwaPowiatu']
      subject = "Rozpoczęto ćwiczenie 9"
      date = datetime.datetime.now().strftime("%d.%m.%Y %H:%M:%S")
      message = f'Drogi uzytkowniku {receiver_email}, o godzinie {date} rozpoczeto przetwarzanie danych dla ppwiatu {county_name}'
      header = f'To: {receiver_email}\nFrom: {sender_email}\nSubject: {subject}\n'
      mess  = f'{header}\n{message}\n\n'
      mail = mess.encode('utf-8')

      port = 587
      server = "smtp.gmail.com"
      ssmtp = smtplib.SMTP(server, port)
      ssmtp.ehlo()
      ssmtp.starttls()
      ssmtp.ehlo()
      ssmtp.login(sender_email, password)
      ssmtp.sendmail(receiver_email, sender_email, mail)
      ssmtp.close()
Shutdown Python:
      import smtplib
      import fme
      import datetime

      sender_email =  fme.macroValues['email']
      receiver_email = fme.macroValues['emailKlienta']
      password = fme.macroValues['Hasło']
      county_name = fme.macroValues['nazwaPowiatu']
      subject = "Zakończono ćwiczenie 9"
      date = datetime.datetime.now().strftime("%d.%m.%Y %H:%M:%S")
      message = f'Drogi uzytkowniku {receiver_email}, o godzinie {date} ukończono z powodzeniem przetwarzanie danych dla ppwiatu {county_name}'
      header = f'To: {receiver_email}\nFrom: {sender_email}\nSubject: {subject}\n'
      mess  = f'{header}\n{message}\n\n'
      mail = mess.encode('utf-8')

      port = 587
      server = "smtp.gmail.com"
      ssmtp = smtplib.SMTP(server, port)
      ssmtp.ehlo()
      ssmtp.starttls()
      ssmtp.ehlo()
      ssmtp.login(sender_email, password)
      ssmtp.sendmail(receiver_email, sender_email, mail)
      ssmtp.close()

Parameters:
- email = jula3465@gmail.com   # e-mail
- Hasło =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
- emailKlienta = jtulin26@gmail.com   # e-mail klienta
- nazwaPowiatu = powiat Katowice   # Nazwa powiatu
- DataPoczątkowa = 20230710000000   # Data Początkowa
- DataKońcowa = 20230730000000   # Data Końcowa
- SourceDataset_SHAPEFILE = $(FME_MF_DIR)powiaty\powiaty.shp   # Source Esri Shapefile(s)
- cloud_coverage = 50   # Podaj maksymalne pokrycie chmurami (w %)
- DestDataset_GEOTIFF = D:\BazyDanychPrzestrzennych   # Destination GeoTIFF Folder

Readers:
- SHAPEFILE_1: SHAPEFILE from $(SourceDataset_SHAPEFILE)

Writers:
- GEOTIFF_1: GEOTIFF to $(DestDataset_GEOTIFF)

powiaty (reader SHAPEFILE_1)
    attributes: gml_id varchar(254), JPT_SJR_KO varchar(254), JPT_POWIER varchar(254), JPT_KOD_JE varchar(254), JPT_NAZWA_ varchar(254), JPT_ORGAN_ varchar(254), JPT_JOR_ID varchar(254), WERSJA_OD varchar(254), WERSJA_DO varchar(254), WAZNY_OD varchar(254), WAZNY_DO varchar(254), JPT_KOD__1 varchar(254), JPT_NAZWA1 varchar(254), JPT_ORGAN1 varchar(254), JPT_WAZNA_ varchar(254), ID_BUFORA_ varchar(254), ID_BUFORA1 varchar(254), ID_TECHNIC varchar(254), IIP_PRZEST varchar(254), IIP_IDENTY varchar(254), IIP_WERSJA varchar(254), JPT_KJ_IIP varchar(254), JPT_KJ_I_1 varchar(254), JPT_KJ_I_2 varchar(254), JPT_OPIS varchar(254), JPT_SPS_KO varchar(254), ID_BUFOR_1 varchar(254), JPT_ID varchar(254), JPT_POWI_1 varchar(254), JPT_KJ_I_3 varchar(254),
      JPT_GEOMET varchar(254), JPT_GEOM_1 varchar(254), SHAPE_LENG varchar(254), SHAPE_AREA varchar(254), REGON varchar(254), RODZAJ varchar(254)
    -> TestFilter
TestFilter
    DEFAULT_VALUE = <UNFILTERED>
    PASSED_TEST_GROUP_OUTPUT = FIRST
    TEST_LIST = "BOOL_OP,OR,COMPOSITE_TEST,""""""1"""""",TEST_CLAUSE,TEST @Value(JPT_NAZWA_) = $(nazwaPowiatu)",@Value(JPT_NAZWA_) = __nazwaPowiatu_
    @Value(JPT_NAZWA_) = __nazwaPowiatu_ -> Reprojector
Reprojector
    DEST = EPSG:4326
    INTERPOLATION_TYPE_NAME = Nearest Neighbor
    RASTER_CELL_SIZE = Preserve Cells
    RASTER_TOLERANCE = 0.0
    REPROJECTED -> Clipper [CLIPPER]
    REPROJECTED -> BoundingBoxAccumulator
BoundingBoxAccumulator
    ACCUM_ATTRS_NAME = Use Attributes From One Feature
    BOUNDING_BOX -> EarthCacheConnector
EarthCacheConnector
    api_key =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
    end_date = $(DataKońcowa)
    interval = 7
    min_aoi_coverage_percentage = $(cloud_coverage)
    output_id = rgbn-a3e8-11e7-9793-ae4260ee3b4b
    pipeline_name = Sentinel4$(nazwaPowiatu)
    start_date = $(DataPoczątkowa)
    -> Sampler_3
Sampler_3
    RATE = 1
    SAMPLE_MODE = No
    SAMPLE_TYPE_LONG = First N Features
    SAMPLED -> RasterBandSeparator_2
RasterBandSeparator_2
    BAND_INDEX_FIELD = _band_index
    PALETTE_INDEX_FIELD = _palette_index
    RASTER_INDEX_FIELD = _raster_index
    SPLIT_BY_NAME = Band and Palette
    -> TestFilter_RED
    -> TestFilter_NIR
TestFilter_RED
    DEFAULT_VALUE = <UNFILTERED>
    PASSED_TEST_GROUP_OUTPUT = FIRST
    TEST_LIST = "BOOL_OP,OR,COMPOSITE_TEST,""""""1"""""",TEST_CLAUSE,TEST @Value(_band_index) = 0",@Value(_band_index) = 0
    @Value(_band_index) = 0 -> NDVICalculator [Red]
TestFilter_NIR
    DEFAULT_VALUE = <UNFILTERED>
    PASSED_TEST_GROUP_OUTPUT = FIRST
    TEST_LIST = "BOOL_OP,OR,COMPOSITE_TEST,""""""1"""""",TEST_CLAUSE,TEST @Value(_band_index) = 3",@Value(_band_index) = 3
    @Value(_band_index) = 3 -> NDVICalculator [Infrared]
NDVICalculator
    COLORIZE = Blue-Yellow-Green Palette
    INDEXTYPE = NDVI
    SAVIADJUSTMENT = 0.5
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterStatisticsCalculator
    INSIDE -> powiaty (writer GEOTIFF_1)
powiaty (writer GEOTIFF_1)
    attributes: gml_id char(254), JPT_SJR_KO char(254), JPT_POWIER char(254), JPT_KOD_JE char(254), JPT_NAZWA_ char(254), JPT_ORGAN_ char(254), JPT_JOR_ID char(254), WERSJA_OD char(254), WERSJA_DO char(254), WAZNY_OD char(254), WAZNY_DO char(254), JPT_KOD__1 char(254), JPT_NAZWA1 char(254), JPT_ORGAN1 char(254), JPT_WAZNA_ char(254), ID_BUFORA_ char(254), ID_BUFORA1 char(254), ID_TECHNIC char(254), IIP_PRZEST char(254), IIP_IDENTY char(254), IIP_WERSJA char(254), JPT_KJ_IIP char(254), JPT_KJ_I_1 char(254), JPT_KJ_I_2 char(254), JPT_OPIS char(254), JPT_SPS_KO char(254), ID_BUFOR_1 char(254), JPT_ID char(254), JPT_POWI_1 char(254), JPT_KJ_I_3 char(254),
      JPT_GEOMET char(254), JPT_GEOM_1 char(254), SHAPE_LENG char(254), SHAPE_AREA char(254), REGON char(254), RODZAJ char(254)
RasterStatisticsCalculator
    RASTER_LEVEL = BAND_ONLY
    RASTER_STATS = "0   MEAN   STDEV   "
